# TestCases

## TC-GS-001: Recipe count verification (Functional)
Load 8 distinct recipe selections via the HMI; confirm each produces a batch. Pass: all 8 produce nominal output.
- Rationale: Verifies SR-GS-001

## TC-GS-002: Throughput test (Functional)
Run kitchen at full demand for 1 hour with representative recipe mix. Measure bowls completed. Pass: at least 200 bowls.
- Rationale: Verifies SR-GS-002

## TC-GS-003: Automation level audit (Functional)
Record time spent in manual mode per component over a 24 h representative shift. Compute automationLevel per component. Pass: mean at least 0.80.
- Rationale: Verifies SR-GS-003

## TC-GS-004: Concurrent operator count (Functional)
Observe crew present on the kitchen floor at peak demand. Pass: at most 5 simultaneous operators required.
- Rationale: Verifies SR-GS-004

## TC-GS-005: Shipping manifest generation (Functional)
Complete one batch; inspect the generated manifest record. Pass: manifest exists with batchId, destination, timestamp, carrier.
- Rationale: Verifies SR-GS-005

## TC-GS-006: Transport loading time (Functional)
Time from end-of-packaging to loaded-on-transport for 20 consecutive batches. Pass: all at most 10 min.
- Rationale: Verifies SR-GS-006

## TC-GS-007: Contamination detection sensitivity (Functional)
Inject 100 spiked batches with known contaminant and 100 clean. Measure true-positive rate. Pass: at least 99%.
- Rationale: Verifies SR-GS-007

## TC-GS-008: Serving temperature (Functional)
Measure soup temperature immediately before sealing, across 50 batches. Pass: all samples in 70-95 deg C.
- Rationale: Verifies SR-GS-008

## TC-GS-009: Container seal-life (Functional)
Seal 30 containers; store under simulated 30-day interstellar transit. Inspect for leaks and spoilage. Pass: 0 leaks, acceptable shelf-life.
- Rationale: Verifies SR-GS-009

## TC-GS-010: Inventory accuracy (Functional)
Physically count stored stock; compare against InventoryState. Pass: abs(actual - recorded) / recorded at most 1%.
- Rationale: Verifies SR-GS-010

## TC-GS-015: Gravity operating range (Functional)
Run full functional test cycle at 0.1, 1, 6, and 12 g on centrifuge-simulator rig. Pass: all functions nominal at each setting.
- Rationale: Verifies SR-GS-015

## TC-GS-016: Structural 12 g tolerance (Functional)
Subject structure to sustained 12 g loading on shake table or via FEA. Inspect for permanent deformation. Pass: FoS at least 1.5, no yield.
- Rationale: Verifies SR-GS-016
