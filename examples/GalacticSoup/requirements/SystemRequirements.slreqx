# SystemRequirements

## SR-GS-001: Recipe count (Functional)
System shall cook at least 8 distinct recipes selectable at runtime.
- Rationale: Eight recipes gives menu variety while staying within ingredient storage and recipe-validation budgets.

## SR-GS-002: Throughput (Functional)
System shall sustain total throughput of at least 200 bowls/hour.
- Rationale: 200 bowls/hour matches expected peak order rate aggregated across customer worlds.

## SR-GS-003: Automation level (Functional)
System shall achieve average automation level of at least 0.8 across components.
- Rationale: 0.8 automation lets the 5-operator crew cover a 24/7 facility with rotation and breaks.

## SR-GS-004: Operator count (Functional)
System shall require at most 5 concurrent operators at peak load.
- Rationale: Facility berthing and life support are sized for a 5-person crew.

## SR-GS-005: Shipping manifest (Functional)
System shall generate a shipping manifest per batch including destination.
- Rationale: Manifest is required for customs, transport routing, and recipient confirmation on delivery.

## SR-GS-006: Transport loading time (Functional)
System shall load packaged soup onto transport within 10 minutes of packaging.
- Rationale: 10-minute window keeps loading pipeline aligned with the 200 bowls/hour production rate.

## SR-GS-007: Contamination detection (Functional)
System shall detect contamination before sealing with at least 99% sensitivity.
- Rationale: 99% sensitivity balances false-positive rework cost against the downstream cost of a contaminated shipment.

## SR-GS-008: Serving temperature (Functional)
System shall verify soup temperature in 70-95 C before QC sign-off.
- Rationale: 70-95 C is the safe serving range: above pathogen-kill threshold and below scald risk.

## SR-GS-009: Container seal life (Functional)
System shall seal containers rated for 30-day interstellar transit.
- Rationale: 30 days covers typical transit time to the farthest customer worlds with margin.

## SR-GS-010: Inventory accuracy (Functional)
System shall track ingredient inventory with at most 1% stock error.
- Rationale: 1% stock error keeps reorder decisions accurate enough to avoid production-halting stock-outs.

## SR-GS-011: Mass budget (Functional)
Total system mass shall not exceed 15000 kg.
- Rationale: Allocated from the facility deployment mass budget.

## SR-GS-012: Power budget (Functional)
Total system power draw shall not exceed 500 kW.
- Rationale: Allocated from the facility power budget.

## SR-GS-013: Cost budget (Functional)
Total system cost shall not exceed 2000000 credits.
- Rationale: Allocated from the facility capital cost budget.

## SR-GS-014: Volume budget (Functional)
Total system volume shall not exceed 400 m^3.
- Rationale: Allocated from the facility floor-space and volume budget.

## SR-GS-015: Gravity operating range (Functional)
System shall perform all cooking, packaging, and shipping functions nominally across ambient gravity 0.1 g to 12 g.
- Rationale: 0.1-12 g spans the full ambient gravity range across candidate customer worlds.

## SR-GS-016: Structural 12 g tolerance (Functional)
System structure and mounts shall withstand sustained 12 g loading without permanent deformation.
- Rationale: 12 g is the worst-case sustained ambient gravity among customer worlds.
