# SystemRequirements

## SR-FCS-001: Roll rate command range (Functional)
The FCS shall accept roll rate commands in the range -180 to +180 deg/s from the pilot inceptors.
- Rationale: Covers the full aerobatic roll envelope.

## SR-FCS-002: Pitch rate command range (Functional)
The FCS shall accept pitch rate commands in the range -30 to +30 deg/s from the pilot inceptors.
- Rationale: Covers normal and emergency pitch maneuvers.

## SR-FCS-003: Yaw rate command range (Functional)
The FCS shall accept yaw rate commands in the range -30 to +30 deg/s from the pilot inceptors.
- Rationale: Covers coordinated turns and crosswind operations.

## SR-FCS-004: Pitch attitude hold accuracy (Functional)
The FCS shall maintain pitch attitude within 0.5 deg of the commanded value in steady-state at all airspeeds within the normal flight envelope.
- Rationale: Minimum accuracy for instrument flight procedures.

## SR-FCS-005: Roll attitude hold accuracy (Functional)
The FCS shall maintain roll attitude within 1.0 deg of the commanded value in steady-state at all airspeeds within the normal flight envelope.
- Rationale: Minimum accuracy for instrument flight procedures.

## SR-FCS-006: Control loop stability margins (Functional)
The FCS shall provide a minimum phase margin of 45 deg and gain margin of 6 dB at all control loop crossover frequencies.
- Rationale: Standard robustness margins for flight control; complies with MIL-HDBK-1797.

## SR-FCS-007: Control loop execution rate (Functional)
The FCS control laws shall execute at a minimum rate of 100 Hz.
- Rationale: Required to achieve Level 1 bandwidth per MIL-STD-1797.

## SR-FCS-008: End-to-end command latency (Functional)
The FCS shall respond to pilot inceptor inputs with an end-to-end latency not exceeding 100 ms, measured from inceptor deflection to control surface position change.
- Rationale: Required for Level 1 handling qualities; excessive latency degrades pilot-vehicle coupling.

## SR-FCS-009: Redundant computation (Functional)
The FCS shall implement dual-redundant flight computers with automatic failover upon detection of a failure in the active channel.
- Rationale: Ensures continued flight control following a single computer failure.

## SR-FCS-010: Failure detection latency (Functional)
The FCS shall detect and isolate a single hardware failure within 50 ms of occurrence.
- Rationale: Limits crew exposure time after a failure; aligns with DO-178C objectives.

## SR-FCS-011: Power supply redundancy (Functional)
The FCS shall operate from a minimum of two electrically independent power supply paths, with automatic switchover upon loss of the primary path.
- Rationale: Power loss must not result in loss of flight control capability.

## SR-FCS-012: Built-in test coverage (Functional)
The FCS built-in test equipment (BITE) shall achieve a fault detection coverage of no less than 95% of all detectable faults during power-on and continuous monitoring.
- Rationale: Reduces reliance on external test equipment and shortens fault isolation time.

## SR-FCS-013: Maintenance data bus (Functional)
The FCS shall provide a maintenance data bus interface compliant with ARINC 604 for interrogation by standard ground support equipment.
- Rationale: Enables use of common GSE across the fleet; reduces training burden.

## SR-FCS-014: Total power budget (Functional)
The total electrical power consumed by all FCS equipment shall not exceed 450 W.
- Rationale: Platform power bus allocation for avionics; margin held by aircraft integrator.

## SR-FCS-015: Total mass budget (Functional)
The total mass of all FCS equipment shall not exceed 35 kg.
- Rationale: Structural mass allocation from the aircraft weight and balance budget.
