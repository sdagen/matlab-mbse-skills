# StakeholderNeeds

## SN-FCS-001: Pilot attitude command (Functional)
The pilot shall be able to command aircraft attitude in roll, pitch, and yaw using the control inceptors.
- Rationale: Primary control function of the FCS; enables the pilot to maneuver the aircraft.

## SN-FCS-002: Aircraft stability (Functional)
The FCS shall maintain aircraft stability across the normal flight envelope without continuous pilot intervention.
- Rationale: Reduces pilot workload and prevents departures from controlled flight.

## SN-FCS-003: Handling qualities (Functional)
The FCS shall provide handling qualities meeting Level 1 criteria as defined in MIL-STD-1797.
- Rationale: Level 1 handling qualities are required for operational effectiveness and pilot acceptance.

## SN-FCS-004: Failure safety (Functional)
No single hardware or software failure shall result in loss of controlled flight.
- Rationale: Mandatory safety requirement for airworthiness certification.

## SN-FCS-005: Maintainability (Functional)
The FCS shall be maintainable in the field using standard ground support equipment.
- Rationale: Reduces life-cycle cost and aircraft downtime.

## SN-FCS-006: Platform SWaP constraints (Functional)
The FCS shall fit within the aircraft platform allocations for electrical power and equipment mass.
- Rationale: The host aircraft imposes fixed power bus capacity and structural mass limits on installed avionics.
