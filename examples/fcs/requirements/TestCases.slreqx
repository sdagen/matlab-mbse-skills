# TestCases

## TC-FCS-001: Roll rate command acceptance (Functional)
Apply roll rate commands at -180, 0, and +180 deg/s via the pilot inceptor interface. Verify that the FCS accepts and processes all commands without saturation or rejection.
- Rationale: Verifies SR-FCS-001

## TC-FCS-002: Pitch rate command acceptance (Functional)
Apply pitch rate commands at -30, 0, and +30 deg/s via the pilot inceptor interface. Verify that the FCS accepts and processes all commands without saturation or rejection.
- Rationale: Verifies SR-FCS-002

## TC-FCS-003: Yaw rate command acceptance (Functional)
Apply yaw rate commands at -30, 0, and +30 deg/s via the pilot inceptor interface. Verify that the FCS accepts and processes all commands without saturation or rejection.
- Rationale: Verifies SR-FCS-003

## TC-FCS-004: Pitch attitude hold accuracy (Functional)
Command a series of pitch attitudes across the flight envelope. After transient settling, record steady-state pitch error. Pass criterion: error not exceeding 0.5 deg at all test points.
- Rationale: Verifies SR-FCS-004

## TC-FCS-005: Roll attitude hold accuracy (Functional)
Command a series of roll attitudes across the flight envelope. After transient settling, record steady-state roll error. Pass criterion: error not exceeding 1.0 deg at all test points.
- Rationale: Verifies SR-FCS-005

## TC-FCS-006: Control loop stability margins (Functional)
Inject frequency sweeps at each control loop breakout point. Compute open-loop frequency response. Pass criterion: phase margin of at least 45 deg and gain margin of at least 6 dB at all crossover frequencies.
- Rationale: Verifies SR-FCS-006

## TC-FCS-007: Control loop execution rate (Functional)
Instrument the flight computer control law task. Record execution timestamps over 10 seconds of operation. Pass criterion: measured rate of at least 100 Hz with jitter not exceeding 1 ms.
- Rationale: Verifies SR-FCS-007

## TC-FCS-008: End-to-end command latency (Functional)
Apply a step input at the pilot inceptor and record control surface position response using high-speed data acquisition. Pass criterion: time from inceptor deflection to first surface movement not exceeding 100 ms.
- Rationale: Verifies SR-FCS-008

## TC-FCS-009: Automatic failover on computer failure (Functional)
With the system operational, inject a simulated primary flight computer failure. Verify that the standby channel assumes control. Pass criterion: flight control maintained with no pilot intervention; failover logged.
- Rationale: Verifies SR-FCS-009

## TC-FCS-010: Failure detection latency (Functional)
Inject a single hardware fault at a known test point. Measure time from fault injection to BITE fault flag assertion. Pass criterion: detection and isolation not exceeding 50 ms.
- Rationale: Verifies SR-FCS-010

## TC-FCS-011: Power supply redundancy and switchover (Functional)
With the system operational, remove primary power. Verify that secondary power path activates and flight control is maintained. Pass criterion: no loss of control; switchover time not exceeding 20 ms.
- Rationale: Verifies SR-FCS-011

## TC-FCS-012: BITE fault detection coverage (Functional)
Execute the BITE test sequence against the fault catalogue. Record detected vs total detectable faults. Pass criterion: detection coverage of at least 95%.
- Rationale: Verifies SR-FCS-012

## TC-FCS-013: Maintenance data bus compliance (Functional)
Connect standard ARINC 604-compliant GSE to the maintenance bus port. Execute the standard interrogation sequence. Pass criterion: all mandatory ARINC 604 labels transmitted and received within timing tolerances.
- Rationale: Verifies SR-FCS-013
